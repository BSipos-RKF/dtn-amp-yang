submodule amp-types {
	belongs-to amp-adm {
		prefix "amp";
	}
	
    organization
        "IETF Delay Tolerant Networking Working Group";
    contact
        "WG Web: <http://tools.ietf.org/wg/dtn/>
        WG List: <mailto:dtn@ietf.org>

        WG Chairs: Brian Haberman
                   <mailto:brian@innovationslab.net>
                   Marc Blanchet
                   <mailto:Marc.Blanchet@viagenie.ca>

        Editor: Brian Sipos
                <mailto:BSIpos@rkf-eng.com>";
    
	description
		"This submodule contains the set of core types necessary to "
		+"define an Asynchronous Management Protocol data model.";
	reference "draft Asynchronous Management Protocol";
	
    revision "2016-04-01" {
        description "Updated to fix typos.";
        reference "I-D draft-bsipos-dtn-amp-yang";
    }
    revision "2016-03-14" {
        description "Initial draft release.";
        reference "I-D draft-bsipos-dtn-amp-yang";
    }
    
	// These extensions are only used within this submodule for annotation
	extension amp-type-id {
		argument "num";
		description "Internal annotation of the AMP ID number of a type.";
	}
	extension amp-type-item {
		argument "name";
		description "Internal annotation of a sub-type item.";
	}
	extension amp-type-list {
		argument "name";
		description "Internal annotation of a sub-type list-of-items.";
	}
	
	typedef "BYTE" {
		type "uint8";
		amp:amp-type-id 0;
		reference "draft Asynchronous Management Protocol";
	}
	typedef "INT" {
		type "int32";
		amp:amp-type-id 1;
		reference "draft Asynchronous Management Protocol";
	}
	typedef "UINT" {
		type "uint32";
		amp:amp-type-id 2;
		reference "draft Asynchronous Management Protocol";
	}
	typedef "VAST" {
		type "int64";
		amp:amp-type-id 3;
		reference "draft Asynchronous Management Protocol";
	}
	typedef "UVAST" {
		type "uint64";
		amp:amp-type-id 4;
		reference "draft Asynchronous Management Protocol";
	}
	typedef "REAL32" {
		type "binary";
		amp:amp-type-id 5;
		description
			"Binary encoding of IEEE-754 32-bit floating point number.";
		reference "draft Asynchronous Management Protocol";
	}
	typedef "REAL64" {
		type "binary";
		amp:amp-type-id 6;
		description
			"Binary encoding of IEEE-754 64-bit floating point number.";
		reference "draft Asynchronous Management Protocol";
	}
	typedef "SDNV" {
		type "binary";
		amp:amp-type-id 9;
		description
			"Binary encoding of self-delimited numeric value.";
		reference "draft Asynchronous Management Protocol";
	}
	typedef "STR" {
		type "string";
		amp:amp-type-id 7;
		description
			"Same UTF-8 encoding as YANG base type. "
			+"Must be zero-terminated.";
		reference "draft Asynchronous Management Protocol";
	}
	
	typedef "TS" {
		type "binary";
		amp:amp-type-id 10;
		description "A timestamp value.";
		reference "draft Asynchronous Management Protocol";
	}
	
	typedef "MID" {
		type "binary";
		amp:amp-type-id 12;
		description "The basic managed-identifier definition.";
		reference "draft Asynchronous Management Protocol";
	}
	
	typedef "BLOB" {
		type "binary";
		amp:amp-type-id 8;
		description
			"The BLOB type should be used as a base type for "
			+"applicaiton-specific types used in data models.";
		reference "draft Asynchronous Management Protocol";
		
		amp:amp-type-item "count" { type "SDNV"; }
		amp:amp-type-list "octets" { type "BYTE"; }
	}
	
	typedef "DC" {
		type "binary";
		amp:amp-type-id 11;
		
		amp:amp-type-item "count" { type "SDNV"; }
		amp:amp-type-list "items" { type "BLOB"; }
	}
	typedef "TDC" {
		type "binary";
		amp:amp-type-id 18;
		
		amp:amp-type-item "entry-count" { type "SDNV"; }
		// These really need not be BLOBs with internal sizes
		amp:amp-type-item "entry-types" { type "BLOB"; }
		amp:amp-type-list "entry-values" { type "BLOB"; }
	}
	typedef "MC" {
		type "binary";
		amp:amp-type-id 13;
		description "Ordered list of MID values.";
		
		amp:amp-type-item "count" { type "SDNV"; }
		amp:amp-type-list "values" { type "MID"; }
	}
	
	// Should be pure MC with no type-id?
	// The only time [EXPR] type is used in AMP spec is 
	// for DEF definition, which is unambiguous on type.
	typedef "EXPR" {
		type "binary";
		amp:amp-type-id 14;
		description
			"Ordered list of MID values representing a "
			+"postfix arithmetic.";
		
		amp:amp-type-item "expression" { type "MC"; }
	}
	// PRED is not a type
	typedef "DEF" {
		type "binary";
		amp:amp-type-id 15;
		description
			"Ordered list of MID values with a corresponding result"
			+"type and overall OID";
		
		amp:amp-type-item "id" { type "MID"; }
		amp:amp-type-item "type" { type "BYTE"; }
		amp:amp-type-item "definition" { type "MC"; }
	}
	typedef "TRL" {
		type "binary";
		amp:amp-type-id 16;
		description
			"Identify and define a time-based macro rule.";
		
		amp:amp-type-item "id" { type "MID"; }
		amp:amp-type-item "start" { type "TS"; }
		amp:amp-type-item "period" { type "SDNV"; units "seconds"; }
		amp:amp-type-item "count" { type "SDNV"; }
		amp:amp-type-item "action" { type "MC"; }
	}
	typedef "SRL" {
		type "binary";
		amp:amp-type-id 17;
		description
			"Identify and define a state-based macro rule.";
		
		amp:amp-type-item "id" { type "MID"; }
		amp:amp-type-item "start" { type "TS"; }
		// Mismatch in AMP spec for PRED type
//		amp:amp-type-item "condition" { type "PRED"; }
		amp:amp-type-item "condition" { type "EXPR"; }
		amp:amp-type-item "count" { type "SDNV"; }
		amp:amp-type-item "action" { type "MC"; }
	}
	// Should be pure TDC with no type-id?
	// The only time [RPT] is used, the RPT type is unnecessary 
	// because there is no alternative but RPT (i.e. TDC) data.
	typedef "RPT" {
		type "binary";
		amp:amp-type-id 19;
		description
			"Identify and define a report template.";
		
		// how is this different from TDC type + MID?
		amp:amp-type-item "id" { type "MID"; }
		amp:amp-type-item "entry-count" { type "SDNV"; }
		// These really need not be BLOBs with internal sizes?
		amp:amp-type-item "entry-types" { type "BLOB"; }
		amp:amp-type-list "entry-values" { type "BLOB"; }
	}
	// May be useful to define a protocol-level CONFIGURE type which 
	// looks similar to...
	//typedef CFG {
	//	amp:amp-type-item "target-id" { type "MID"; }
	//	amp:amp-type-list "value" { type "BLOB"; }
	//}
	// This would allow a simple macro of CFG values
	
	// Should be pure DEF with no type-id?
	// The only time MACRO is used is not for encoding, but for 
	// typing objects in OID tree.
	typedef "MACRO" {
		type "DEF";
		amp:amp-type-id 20;
		description "Ordered list of control/macro MID values.";
	}
	typedef "UNK" {
		type "binary";
		amp:amp-type-id 21;
	}
}
